#El objeto seleccionado se vuelve un 50% transparente si no tiene transparencia y se le quita la transparencia si la tiene.

transparentando = False

objetosSeleccionados=Gui.Selection.getSelection()
for objeto in objetosSeleccionados:
    transparencia=objeto.ViewObject.Transparency
    if transparencia == 0:
        objeto.ViewObject.Transparency=50
        transparentando = True

if transparentando == False:
    for objeto in objetosSeleccionados:
        objeto.ViewObject.Transparency=0
